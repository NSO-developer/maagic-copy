module test-maagic-copy {
  yang-version "1.1";

  namespace "http://example.com/test-maagic-copy";
  prefix test-maagic-copy;

  import ietf-inet-types {
    prefix inet;
  }
  import tailf-common {
    prefix tailf;
  }
  import tailf-ncs {
    prefix ncs;
  }

  description
    "A model for testing the maagic-copy package";

  revision 2020-03-09 {
    description
      "Initial revision.";
  }

  grouping simple {
    container simple {
      leaf a-leaf {
        type string;
      }

      list a-list {
        key name;

        leaf name {
          type string;
        }
      }

      leaf-list string-list {
        type string;
      }

      leaf-list id-list {
        type instance-identifier;
      }

      container a-container {
        leaf another-leaf {
          type string;
        }
      }

      grouping presence-cont-grouping {
        container presence-container {
          leaf system {
            type inet:uri;
            default "IETF-2015 model";
          }
          leaf x-coordinate {
            type decimal64 {
              fraction-digits 16;
            }
          }
          leaf y-coordinate {
            type decimal64 {
              fraction-digits 16;
            }
          }
        }
      }

      uses presence-cont-grouping {
        refine presence-container {
          presence "Presence container";
        }
      }

      choice a-choice {
        leaf first-choice {
          type string;
        }
        leaf second-choice {
          type string;
        }
      }
      container test-when {
        leaf condition {
          type string;
        }
        leaf addition {
          type empty;
          when "../condition";
        }
        leaf condition2 {
          type enumeration {
            enum a;
            enum b;
            enum c;
          }
        }
        leaf addition2 {
          type empty;
          when "../condition2 = 'a' or ../condition2 = 'b'";
        }
      }
    }
  }

  container src {
    uses simple;
    action test-action {
      tailf:actionpoint "test-action";
      input {
        uses simple;
      }
      output {
        uses simple;
      }
    }
  }

  container dst {
    uses simple;
  }
}
